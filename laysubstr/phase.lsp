(defun c:ls-1 (/ lyname msg) 
    (setq lyname "*-1"
          msg    "Phase 1"
    )
    (laysubstr lyname msg)
)
(defun c:ls-2 (/ lyname msg) 
    (setq lyname "*-2"
          msg    "Phase 2"
    )
    (laysubstr lyname msg)
)
(defun c:ls-3 (/ lyname msg) 
    (setq lyname "*-3"
          msg    "Phase 3"
    )
    (laysubstr lyname msg)
)
(defun c:ls-4 (/ lyname msg) 
    (setq lyname "*-4"
          msg    "Phase 4"
    )
    (laysubstr lyname msg)
)
(defun c:ls-5 (/ lyname msg) 
    (setq lyname "*-5"
          msg    "Phase 5"
    )
    (laysubstr lyname msg)
)
(defun c:ls-6 (/ lyname msg) 
    (setq lyname "*-6"
          msg    "Phase 6"
    )
    (laysubstr lyname msg)
)
(defun c:ls-7 (/ lyname msg) 
    (setq lyname "*-7"
          msg    "Phase 7"
    )
    (laysubstr lyname msg)
)
(defun c:ls-8 (/ lyname msg) 
    (setq lyname "*-8"
          msg    "Phase 8"
    )
    (laysubstr lyname msg)
)
(defun c:ls-9 (/ lyname msg) 
    (setq lyname "*-9"
          msg    "Phase 9"
    )
    (laysubstr lyname msg)
)
(defun c:ls-Neww (/ lyname msg) 
    (setq lyname "*-N"
          msg    "New Work"
    )
    (laysubstr lyname msg)
)
(defun c:ls-Exst (/ lyname msg) 
    (setq lyname "*-E"
          msg    "Existing to remain"
    )
    (laysubstr lyname msg)
)
(defun c:ls-Demo (/ lyname msg) 
    (setq lyname "*-D"
          msg    "Existing to Demolish"
    )
    (laysubstr lyname msg)
)
(defun c:ls-Move (/ lyname msg) 
    (setq lyname "*-M"
          msg    "Item to be Moved"
    )
    (laysubstr lyname msg)
)
(defun c:ls-Abnd (/ lyname msg) 
    (setq lyname "*-A"
          msg    "Abandonned"
    )
    (laysubstr lyname msg)
)
(defun c:ls-Rfsh (/ lyname msg) 
    (setq lyname "*-R"
          msg    "Refurbished"
    )
    (laysubstr lyname msg)
)
(defun c:ls-Temp (/ lyname msg) 
    (setq lyname "*-T"
          msg    "Temporary"
    )
    (laysubstr lyname msg)
)
(defun c:ls-Prow (/ lyname msg) 
    (setq lyname "*-P"
          msg    "Proposed Work"
    )
    (laysubstr lyname msg)
)
(defun c:ls-Futw (/ lyname msg) 
    (setq lyname "*-F"
          msg    "Futur Work "
    )
    (laysubstr lyname msg)
)
(defun c:ls-Save (/ lyname msg) 
    (setq lyname "*-S"
          msg    "Existing to be Saved"
    )
    (laysubstr lyname msg)
)
