(defun c:ls-Patt (/ lyname msg) 
    (setq lyname "*Patt*"
          msg    "hatch patterns"
    )
    (laysubstr lyname msg)
)
(defun c:ls-Labl (/ lyname msg) 
    (setq lyname "*Labl*"
          msg    "labels"
    )
    (laysubstr lyname msg)
)
(defun c:ls-Tags (/ lyname msg) 
    (setq lyname "*Tags*"
          msg    "tags"
    )
    (laysubstr lyname msg)
)
(defun c:ls-Note (/ lyname msg) 
    (setq lyname "*Note*"
          msg    "notes"
    )
    (laysubstr lyname msg)
)
(defun c:ls-Text (/ lyname msg) 
    (setq lyname "*Text*"
          msg    "texts"
    )
    (laysubstr lyname msg)
)
(defun c:ls-Iden (/ lyname msg) 
    (setq lyname "*Iden*"
          msg    "identifications"
    )
    (laysubstr lyname msg)
)
(defun c:ls-Revc (/ lyname msg) 
    (setq lyname "*Revc*"
          msg    "revision clouds"
    )
    (laysubstr lyname msg)
)
(defun c:ls-Revs (/ lyname msg) 
    (setq lyname "*Revs*"
          msg    "revision indicators and text"
    )
    (laysubstr lyname msg)
)
(defun c:ls-Refr (/ lyname msg) 
    (setq lyname "*Refr*"
          msg    "external reference files"
    )
    (laysubstr lyname msg)
)
(defun c:ls-Scrn (/ lyname msg) 
    (setq lyname "*Scrn*"
          msg    "backgroud screening"
    )
    (laysubstr lyname msg)
)
(defun c:ls-Symb (/ lyname msg) 
    (setq lyname "*Symb*"
          msg    "symbols"
    )
    (laysubstr lyname msg)
)
(defun c:ls-Dims (/ lyname msg) 
    (setq lyname "*Dims*"
          msg    "dimensions"
    )
    (laysubstr lyname msg)
)
(defun c:ls-Grid (/ lyname msg) 
    (setq lyname "*Grid*"
          msg    "Grids"
    )
    (laysubstr lyname msg)
)
(defun c:ls-Levl (/ lyname msg) 
    (setq lyname "*Levl*"
          msg    "Levels"
    )
    (laysubstr lyname msg)
)
(defun c:ls-Mask (/ lyname msg) 
    (setq lyname "*Mask*"
          msg    "Masking Objects"
    )
    (laysubstr lyname msg)
)
(defun c:ls-Nplt (/ lyname msg) 
    (setq lyname "*Nplt*,Defpoints"
          msg    "Non-plottable reference lines"
    )
    (laysubstr lyname msg)
)
(defun c:ls-0001 (/ lyname msg) 
    (setq lyname "*0001*"
          msg    "Stack Number 1"
    )
    (laysubstr lyname msg)
)
(defun c:ls-0002 (/ lyname msg) 
    (setq lyname "*0002*"
          msg    "Stack Number 2"
    )
    (laysubstr lyname msg)
)
(defun c:ls-0003 (/ lyname msg) 
    (setq lyname "*0003*"
          msg    "Stack Number 3"
    )
    (laysubstr lyname msg)
)
(defun c:ls-0004 (/ lyname msg) 
    (setq lyname "*0004*"
          msg    "Stack Number 4"
    )
    (laysubstr lyname msg)
)
(defun c:ls-0005 (/ lyname msg) 
    (setq lyname "*0005*"
          msg    "Stack Number 5"
    )
    (laysubstr lyname msg)
)
(defun c:ls-0006 (/ lyname msg) 
    (setq lyname "*0006*"
          msg    "Stack Number 6"
    )
    (laysubstr lyname msg)
)
(defun c:ls-0007 (/ lyname msg) 
    (setq lyname "*0007*"
          msg    "Stack Number 7"
    )
    (laysubstr lyname msg)
)
(defun c:ls-0008 (/ lyname msg) 
    (setq lyname "*0008*"
          msg    "Stack Number 8"
    )
    (laysubstr lyname msg)
)
(defun c:ls-0009 (/ lyname msg) 
    (setq lyname "*0009*"
          msg    "Stack Number 9"
    )
    (laysubstr lyname msg)
)
